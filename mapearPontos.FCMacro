import math

zona = Gui.Selection.getSelectionEx()[0] # pegar uma zona somente
zona.Object.Shape.CenterOfMass

p = zona.Object.Points
tamanho = len(p)
g = [[] for i in range(tamanho)] # sentido do giro (horario == negativo e anti-horario == positivo)
gg = 0 # giro geral

for i in range(tamanho):
		g[i] = p[0] - p[i] if i == tamanho - 1 else p[i+1] - p[i]
		g[i] = math.copysign(1,g[i][0])*math.copysign(1,g[i][1])	
		gg += g[i]	

#g = [-1.0, 1.0, -1.0, 1.0, -1.0, -1.0] 
#gg = -2
App.Console.PrintMessage([g,gg])
