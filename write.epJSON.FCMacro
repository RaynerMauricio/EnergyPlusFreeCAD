import json
from PySide import QtGui, QtCore

class inir_gui_class(QtGui.QDialog):
	
	def __init__(self):
		super(inir_gui_class, self).__init__()
		self.initUI()
	def initUI(self):

		self.setGeometry(	250, 250, 400, 250)
		self.setWindowTitle("INI-R 2019 - EnergyPlus v9.1.0 - LABEEE")
		self.setWindowFlags(QtCore.Qt.WindowStaysOnTopHint)

		cancelButton = QtGui.QPushButton('Cancelar', self)
		cancelButton.clicked.connect(self.funCancelar)
		cancelButton.setAutoDefault(True)
		cancelButton.move(150, 200)
		okButton = QtGui.QPushButton('Criar epJSON', self)
		okButton.clicked.connect(self.funepJSON)
		okButton.move(260, 200)
		self.show()


	def funCancelar(self):
		self.close()
		
	def funepJSON(self):
		# caminho do arquivo selecionado
		pathfile = App.ActiveDocument.FileName[:App.ActiveDocument.FileName.rfind('/')+1]
		
		epJSON = {}
		
		# lista das zonas selecionadas
		listaZonas = Gui.Selection.getSelectionEx()
		
		if listaZonas != []:
			
			for cada in range(len(listaZonas)):
		
				zona = listaZonas[cada]
		
				if 'DWire' in zona.ObjectName:
					
					pontos = [list(i) for i in zona.Object.Points]
		
					contorno = zona.Object.Shape.BoundBox
					
					listaXMin, listaYMin, listaZMin = [], [], []
					
					nomeZona = zona.Object.Label.decode()
		
					listaVetores = zona.Object.Shape.Edges
					numeroVetores = len(listaVetores)
		
					for i in listaVetores:
						contorno = i.BoundBox
						listaXMin.append(contorno.XMin)
						listaYMin.append(contorno.YMin)
						listaZMin.append(contorno.ZMin)
		
					XMin = min(listaXMin)
					YMin = min(listaYMin)
					ZMin = min(listaZMin)
		
					origem = [XMin, YMin, ZMin]				

				elif 'Rectangle' in zona.ObjectName:
					
					pontos = []
				 	
					for i in zona.Object.Shape.Edges:
				 		
				 		contorno = i.BoundBox
				 		direcao = list(i.Curve.Direction)
				 		direcao = [i*i for i in direcao]
				
				 		listaXMin, listaYMin, listaZMin = [], [], []
					
				 		listaVetores = zona.Object.Shape.Edges
				 		nomeZona = zona.Object.Label.decode()
				 		numeroVetores = len(listaVetores)
		
				 		for i in listaVetores:
				 			contorno = i.BoundBox
				 			listaXMin.append(contorno.XMin)
				 			listaYMin.append(contorno.YMin)
				 			listaZMin.append(contorno.ZMin)
					
				 		XMin = min(listaXMin)
				 		YMin = min(listaYMin)
				 		ZMin = min(listaZMin)
				 		origem = [XMin, YMin, ZMin]
		
				 		contorno.XMax = contorno.XMax
				 		contorno.YMax = contorno.YMax
				 		contorno.ZMax = contorno.ZMax
				 		contorno.XMin = contorno.XMin
				 		contorno.YMin = contorno.YMin
				 		contorno.ZMin = contorno.ZMin
		
				 		if 1 == math.copysign(1,direcao[0]) and -1 == math.copysign(1,direcao[1]):
				 			pontos.extend([contorno.XMin, contorno.YMax, contorno.ZMin])
				 			pontos.extend([contorno.XMax, contorno.YMin, contorno.ZMax])
				 		else:
				 			pontos.extend([contorno.XMin, contorno.YMin, contorno.ZMin])
				 			pontos.extend([contorno.XMax, contorno.YMax, contorno.ZMax])
				
				else:
					reply = QtGui.QMessageBox.information(None,"","Use DWire ou Rectangle.")
		
				epJSON[nomeZona] = {}
				epJSON[nomeZona]['vetores'] = [[] for i in range(numeroVetores)]
				epJSON[nomeZona]['origem'] = origem
		
				num = 0
				while num < numeroVetores-1:
					epJSON[nomeZona]['vetores'][num] = [pontos[num], pontos[num+1]]
					num += 1
				epJSON[nomeZona]['vetores'][num] = [pontos[num], pontos[0]]
		
		QtGui.QMessageBox.information(None,"","teste")
		json.dump(epJSON, open(pathfile+'geometry.epJSON','w'))
		#App.Console.PrintMessage(pathfile+'geometry.epJSON')

executar = inir_gui_class()
executar.exec_()

'''
#Gui.Selection.getPreselection()
#list(vetor.getPoint(0))
#App.Console.PrintMessage("teste")
#reply = QtGui.QMessageBox.information(None,"","teste")
'''
