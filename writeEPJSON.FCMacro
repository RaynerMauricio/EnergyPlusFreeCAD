import json

# caminho do arquivo selecionado
pathfile = App.ActiveDocument.FileName[:App.ActiveDocument.FileName.rfind('/')+1]

# AllObject
allobject_pathfile = pathfile+"/AllObject/AllObject.V901.epJSON"
allobject = json.loads(open(allobjectpathfile, 'r').read())

# lista das zonas selecionadas
listaZonas = Gui.Selection.getSelection()

# testando para cada zona
listaVetores = listaZonas[0].Shape.Edges

listaXMin = list()
listaYMin = list()
listaZMin = list()

for i in listaVetores:
	vetor = i.BoundBox
	listaXMin.append(vetor.XMin)
	listaYMin.append(vetor.YMin)
	listaZMin.append(vetor.ZMin)

XMin = 0-min(listaXMin)
YMin = 0-min(listaYMin)
ZMin = 0-min(listaZMin)

for i in listaVetores:
	vetor = i.BoundBox
	vetor.XMax = vetor.XMax + XMin
	vetor.YMax = vetor.YMax + YMin
	vetor.ZMax = vetor.ZMax + ZMin
	vetor.XMin = vetor.XMin + XMin
	vetor.YMin = vetor.YMin + YMin
	vetor.ZMin = vetor.ZMin + ZMin

App.Console.PrintMessage([listaXMin,listaYMin])

epJSON = {}

json.dump(epJSON, open(pathfile+'geometry.epJSON','w'))
